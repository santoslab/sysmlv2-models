package GUMBO_Definitions {
  language "GUMBO" /*{
    library
        functions

          def aboveAbsoluteZero(value: AADL_Base_Types::Float_32): AADL_Base_Types::Boolean := f32(-459.67) < value;
  }*/
}
